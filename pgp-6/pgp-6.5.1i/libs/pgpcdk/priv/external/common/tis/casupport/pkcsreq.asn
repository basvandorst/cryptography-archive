-- Author: Michael_Elkins@NAI.com
-- Last modified on January 15, 1999

IMPORTS ContentInfo FROM pkcs7;
IMPORTS Name, GeneralName, ReasonFlags FROM pkix;

PKCSReq ::= SEQUENCE {
	endEntityInfo	EndEntityInfo,
	regInfo		OCTET STRING OPTIONAL
}

-- EndEntityInfo ::= CHOICE {
-- 	pkcs10		CertificationRequest
-- 	signedKey	[0] SignedPublicKeyAndChallenge
-- }

-- we only support PKCS10 for now, and it will be generated outside of our
-- control, so this needs to be defined as ANY
EndEntityInfo ::= ANY

-- Netscape

-- SignedPublicKeyAndChallange ::= SEQUENCE {
-- 	publicKeyAndChallenge	PublicKeyChallenge,
-- 	signatureAlgorithm	AlgorithmIdentifier,
-- 	signature		BIT STRING
-- }

-- PublicKeyAndChallenge ::= SEQUENCE {
-- 	spki		SubjectPublicKeyInfo,
-- 	challenge	IA5String
-- }

--
-- returned certificate format (Verisign CRS)
--
CertRep ::= SEQUENCE {
	certs	ContentInfo OPTIONAL,	-- PKCS#7 certs-only message
	rspInfo	OCTET STRING
}

GetCert ::= SEQUENCE {
	Issuername	Name,
	serialNumber	INTEGER
}

GetCertInitial ::= SEQUENCE {
	issuerAndSubject	IssuerAndSubject,
	reginfo			OCTET STRING OPTIONAL
}

IssuerAndSubject ::= SEQUENCE {
	issuer	Name,
	subject	Name
}

-- from draft-ietf-pkix-cmc-02
GetCRL ::= SEQUENCE {
	issuerName	Name,
	crlName		GeneralName OPTIONAL,
	time		GeneralizedTime OPTIONAL,
	reason		ReasonFlags OPTIONAL
}

-- temporary CRS OID's from VeriSign

verisign OBJECT IDENTIFIER ::= { 2 16 us(840) 1 verisign(113733) }
id-pki OBJECT IDENTIFIER ::= { verisign pki(1) }
id-attributes OBJECT IDENTIFIER ::= { id-pki attribute(9) }

at-pki-message-type OBJECT IDENTIFIER ::= { id-attributes 2 }
at-pki-status OBJECT IDENTIFIER ::= { id-attributes 3 }
at-pki-failinfo OBJECT IDENTIFIER ::= { id-attributes 4 }
at-pki-sendernonce OBJECT IDENTIFIER ::= { id-attributes 5 }
at-pki-recipientnonce OBJECT IDENTIFIER ::= { id-attributes 6 }
at-pki-transactionid OBJECT IDENTIFIER ::= { id-attributes 7 }
at-pki-extensionreq OBJECT IDENTIFIER ::= { id-attributes 8 }
at-pki-version OBJECT IDENTIFIER ::= { id-attributes 9 }
at-pki-dualstatus OBJECT IDENTIFIER ::= { id-attributes 10 }
