IMPORTS AlgorithmIdentifier, Attributes, Version FROM x509;

PrivateKeyInfo ::= SEQUENCE {
  version Version,

  privateKeyAlgorithm PrivateKeyAlgorithmIdentifier,
  privateKey PrivateKey,
  attributes [0] IMPLICIT Attributes OPTIONAL }

-- Version ::= INTEGER

PrivateKeyAlgorithmIdentifier ::= AlgorithmIdentifier

PrivateKey ::= OCTET STRING

-- Attributes ::= SET OF Attribute

EncryptedPrivateKeyInfo ::= SEQUENCE {
  encryptionAlgorithm EncryptionAlgorithmIdentifier,
  encryptedData PKCS8EncryptedData }

EncryptionAlgorithmIdentifier ::= AlgorithmIdentifier

-- unfortunately, PKCS-7 defined EncryptedData to be something else...
PKCS8EncryptedData ::= OCTET STRING
